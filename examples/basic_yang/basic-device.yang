module basic-device {
  yang-version 1.1;
  namespace "urn:example:basic-device";
  prefix bd;

  organization "Example";
  contact "example@example.com";
  description
    "A minimal YANG module used as a basic example.";

  revision 2026-04-23 {
    description
      "Initial revision.";
  }

  grouping interface-optional-settings {
    description
      "Optional interface attributes reused via uses.";

    leaf description {
      type string;
      description "Human-readable interface description.";
    }

    leaf hold-time {
      type uint16 {
        range "0..300";
      }
      description "Link hold-time in seconds.";
    }
  }

  container system {
    description
      "Simple system configuration data.";

    leaf hostname {
      type string;
      must "string-length(.) > 0" {
        error-message "hostname must be non-empty";
      }
      description "Device hostname.";
    }

    leaf enabled {
      type boolean;
      default true;
      description "Whether the system is enabled.";
    }

    leaf management-interface {
      type leafref {
        path "/system/interface/name";
      }
      description "Reference to the interface used for management traffic.";
    }

    leaf management-interface-index {
      type leafref {
        path "/system/interface/if-index";
      }
      description "Reference to the interface index used for management traffic.";
    }

    list interface {
      key "name";
      description "List of network interfaces.";

      uses interface-optional-settings;

      leaf name {
        type string;
        must "string-length(.) > 0" {
          error-message "interface name must be non-empty";
        }
        description "Interface name.";
      }

      leaf if-index {
        type uint16;
        description "Interface index.";
      }

      leaf mtu {
        type uint16 {
          range "576..9216";
        }
        description "Interface MTU.";
      }

      leaf admin-up {
        type boolean;
        default true;
        description "Administrative state of the interface.";
      }

      leaf shutdown-reason {
        when "../admin-up = false()";
        type string;
        description "Required context note when an interface is administratively down.";
      }
    }
  }
}
